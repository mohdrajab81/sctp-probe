-- SBC-AP-Constants.asn
--
-- Taken from 3GPP TS 29.168 V15.1.0 (2018-09)
-- http://www.3gpp.org/ftp/Specs/archive/29_series/29.168/29168-930.zip
--
-- 4.4.7	Constant Definitions
--
-- **************************************************************
--
-- Constant definitions
--
-- **************************************************************

SBC-AP-Constants {
itu-t (0) identified-organization (4) etsi (0) mobileDomain (0) 
eps-Access (21) modules (3) sbc-AP (3) version1 (1) sbc-AP-Constants (4)}

DEFINITIONS AUTOMATIC TAGS ::= 

BEGIN

-- **************************************************************
--
-- Elementary Procedures
--
-- **************************************************************

id-Write-Replace-Warning 	INTEGER ::= 0 
id-Stop-Warning 		INTEGER ::= 1 
id-Error-Indication 	INTEGER ::= 2
id-Write-Replace-Warning-Indication	INTEGER ::= 3
id-Stop-Warning-Indication	INTEGER ::= 4
id-PWS-Restart-Indication	INTEGER ::= 5 
id-PWS-Failure-Indication	INTEGER ::= 6

-- **************************************************************
--
-- IEs
--
-- **************************************************************

id-Broadcast-Message-Content	INTEGER ::= 0
id-Cause 	INTEGER ::= 1
id-Criticality-Diagnostics	INTEGER ::=2
id-Data-Coding-Scheme 	INTEGER ::= 3
id-Failure-List 	INTEGER ::= 4
id-Message-Identifier 	INTEGER ::= 5
id-Number-of-Broadcasts-Completed-List 	INTEGER ::= 6
id-Number-of-Broadcasts-Requested 	INTEGER ::= 7
id-Radio-Resource-Loading-List 	INTEGER ::= 8
id-Recovery-Indication 	INTEGER ::= 9
id-Repetition-Period 	INTEGER ::= 10
id-Serial-Number 	INTEGER ::= 11
id-Service-Areas-List 	INTEGER ::= 12
id-TypeOfError		INTEGER ::= 13
id-List-of-TAIs		INTEGER ::= 14
id-Warning-Area-List 	INTEGER ::= 15
id-Warning-Message-Content	INTEGER ::= 16
id-Warning-Security-Information	INTEGER ::= 17
id-Warning-Type		INTEGER ::= 18 
id-Omc-Id 		INTEGER ::= 19 
id-Concurrent-Warning-Message-Indicator INTEGER ::= 20 
id-Extended-Repetition-Period	INTEGER ::= 21
id-Unknown-Tracking-Area-List	INTEGER ::= 22 
id-Broadcast-Scheduled-Area-List	INTEGER ::= 23
id-Send-Write-Replace-Warning-Indication INTEGER ::= 24
id-Broadcast-Cancelled-Area-List	INTEGER ::= 25
id-Send-Stop-Warning-Indication	INTEGER ::= 26
id-Stop-All-Indicator	INTEGER ::= 27 
id-Global-ENB-ID		INTEGER ::= 28
id-Broadcast-Empty-Area-List	INTEGER ::= 29
id-Restarted-Cell-List	INTEGER ::= 30
id-List-of-TAIs-Restart	INTEGER ::= 31
id-List-of-EAIs-Restart	INTEGER ::= 32 
id-Failed-Cell-List	INTEGER ::= 33
id-List-of-5GS-TAIs	INTEGER ::= 34
id-Warning-Area-List-5GS	INTEGER ::= 35
id-Global-RAN-Node-ID	INTEGER ::= 36
id-Global-GNB-ID	INTEGER ::= 37
id-RAT-Selector-5GS		INTEGER ::= 38
id-Unknown-5GS-Tracking-Area-List	INTEGER ::= 39
id-Broadcast-Scheduled-Area-List-5GS	INTEGER ::= 40
id-Broadcast-Cancelled-Area-List-5GS	INTEGER ::= 41
id-Broadcast-Empty-Area-List-5GS	INTEGER ::= 42
id-Restarted-Cell-List-NR	INTEGER ::= 43
id-Failed-Cell-List-NR	INTEGER ::= 44
id-List-of-5GS-TAI-for-Restart	INTEGER ::= 45
id-Warning-Area-Coordinates	INTEGER ::= 46



-- **************************************************************
--
-- Extension constants
--
-- **************************************************************

-- **************************************************************
--
-- Lists
--
-- **************************************************************

maxNrOfErrors	INTEGER ::= 256 
maxnoofCellID	INTEGER	::= 65535 
maxnoofCellinEAI	INTEGER ::= 65535
maxnoofCellinTAI	INTEGER ::= 65535
maxNrOfTAIs		INTEGER ::= 65535
maxnoofEmergencyAreaID	INTEGER	::= 65535
maxnoofTAIforWarning	INTEGER ::= 65535

maxProtocolExtensions 	INTEGER ::= 65535
maxProtocolIEs	INTEGER ::= 65535 
maxnoofeNBIds	INTEGER ::= 256
maxnoofRestartedCells	INTEGER ::= 256
maxnoofRestartTAIs	INTEGER ::= 2048
maxnoofRestartEAIs	INTEGER ::= 256 
maxnoofFailedCells	INTEGER ::= 256
maxnoof5GSTAIs	INTEGER ::= 2048
maxnoofCellsingNB	INTEGER ::= 16384
maxnoofCellsin5GS	INTEGER ::= 16776960
maxnoofCellsin5GSTAI	INTEGER ::= 65535
maxnoofRANNodes	INTEGER ::= 65535
maxnoofRestart5GSTAIs	INTEGER ::= 2048
maxnoofCellsforRestartNR 	INTEGER ::= 16384


END
